/*
 * Copyright (c) 2017 Juniper Networks, Inc.
 * All rights reserved.
 */

 module junos-extension {
  namespace "http://xml.juniper.net/junos/15.1F6/junos";
  prefix junos;

  import ietf-yang-metadata {
    prefix md;
  }

  organization
    "Juniper Networks, Inc.";

  description
    "This module contains definitions for Junos YANG extensions.";

   extension must {
     argument "stmt-algebra";
     description "
      expression of configuration-statement paths having special
      keywords like any, all, unique";
   }
   extension must-message {
     argument "message-string";
     description "
      When specifying the junos:must constraint, a must-message should
      also be specified so that when the contraint is not met,the
      warning message informs users what the constraints are.

      If the must-message is missing, the input file will compile,
      but the warning message will say (null) which won't be
      helpful for users to fix the problem";
   }
   extension posix-pattern {
     argument "value";
     description "
      expression of pattern in posix format";
   }
   extension pattern-message {
     argument "value";
     description "
      Error message in case of mismatch";
   }

    md:annotation commit-seconds {
        type uint64;
    }

    md:annotation commit-localtime {
        type string;
    }

    md:annotation commit-user {
        type string;
    }
 }
